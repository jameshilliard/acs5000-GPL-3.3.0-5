--
--
-- CSERVER MIB -- V1.0.0 Rev 0b 08/13/2003
--
-- Digital Networks
-- Enterprise MIB for CServer Device Communications Servers
--
--
CSERVER-MIB DEFINITIONS ::= BEGIN

IMPORTS
	InterfaceIndexOrZero, InterfaceIndex
		FROM IF-MIB
	DisplayString
		FROM SNMPv2-TC
	OBJECT-TYPE, MODULE-IDENTITY, OBJECT-IDENTITY, Counter32, IpAddress, Integer32
		FROM SNMPv2-SMI
	dnpgXarchMibs
		FROM DigitalNetworks-MIB;


cSrvMgmt	MODULE-IDENTITY
	LAST-UPDATED	"200308130000Z"
	ORGANIZATION	"Digital Networks"
	CONTACT-INFO	"Digital Networks
			       20 North Wentworth Ave
				 Londonderry, NH 03053
				 USA"
	DESCRIPTION	"This file defines the Digital Network Enteprise MIB for CServer
			 Device Communications Server products."
	REVISION	"200308130000Z"
	DESCRIPTION	"First Draft - CSERVER-MIB"
::= { dnpgXarchMibs 6 }


--
--    CServer MIB Management Groups
--

cSrvSys	OBJECT IDENTIFIER  ::= { cSrvMgmt 1 }

cSrvConf	OBJECT IDENTIFIER  ::= { cSrvMgmt 2 }

cSrvInfo	OBJECT IDENTIFIER  ::= { cSrvMgmt 3 }

cSrvAdm	OBJECT IDENTIFIER  ::= { cSrvMgmt 4 }


--
--    The cSrvSys Group
--

cSrvpname OBJECT-TYPE
	SYNTAX DisplayString
	MAX-ACCESS read-only
	STATUS current
	DESCRIPTION "The product's name - CServerxx (xx - the number of the serial ports )"
::= { cSrvSys 1 }

cSrvversion OBJECT-TYPE
	SYNTAX DisplayString
	MAX-ACCESS read-only
	STATUS current
	DESCRIPTION "The firmware version"
::= {cSrvSys 2}

cSrvPower OBJECT-IDENTITY
	STATUS current
	DESCRIPTION "It gives information about the Power Supply"
::= { cSrvSys 3 }

cSrvPwNum OBJECT-TYPE
	SYNTAX Integer32
	MAX-ACCESS read-only
	STATUS current
	DESCRIPTION "Number of the power supplies"
::= { cSrvPower 1 }

cSrvPw1 OBJECT-TYPE
	SYNTAX INTEGER {
		noinstalled(0),
		powerON(1),
		powerOFF(2)
	}
	MAX-ACCESS read-only
	STATUS current
	DESCRIPTION "State of the first power supply"
::= { cSrvPower 2 }

cSrvPw2 OBJECT-TYPE
	SYNTAX INTEGER {
		noinstalled(0),
		powerON(1),
		powerOFF(2)
	}
	MAX-ACCESS read-only
	STATUS current
	DESCRIPTION "State of the second power supply"
::= { cSrvPower 3 }

cSrvPcmcia OBJECT-IDENTITY
	STATUS current
	DESCRIPTION "PCMCIA card information"
::= {cSrvSys 4}

cSrvNPcmcia OBJECT-TYPE
	SYNTAX Integer32
	MAX-ACCESS read-only
	STATUS current
	DESCRIPTION "Number of the cards PCMCIA available"
::= { cSrvPcmcia 1 }

cSrvCardIdentTable OBJECT-TYPE
	SYNTAX SEQUENCE OF CSrvCardIdentEntry
	MAX-ACCESS not-accessible
	STATUS current
	DESCRIPTION "Card identification"
::= { cSrvPcmcia 2 }

cSrvCardIdentEntry OBJECT-TYPE
	SYNTAX CSrvCardIdentEntry
	MAX-ACCESS not-accessible
	STATUS current
	DESCRIPTION "One particular association between PCMCIA socket and card identification"
	INDEX { cSrvCardIdentIndex }
::= { cSrvCardIdentTable 1 }

CSrvCardIdentEntry ::= SEQUENCE {
	cSrvCardIdentIndex Integer32,
	cSrvCardIdentProd DisplayString,
	cSrvCardIdentMan DisplayString ,
	cSrvCardIdentFunc DisplayString,
	cSrvCardIdentPCI DisplayString
}

cSrvCardIdentIndex OBJECT-TYPE
	SYNTAX Integer32(0..2)
	MAX-ACCESS read-only
	STATUS current
	DESCRIPTION "number to identifier the socket Card"
::= { cSrvCardIdentEntry 1 }

cSrvCardIdentProd OBJECT-TYPE
	SYNTAX DisplayString
	MAX-ACCESS read-only
	STATUS current
	DESCRIPTION "Product identification strings"
::= { cSrvCardIdentEntry 2 }

cSrvCardIdentMan OBJECT-TYPE
	SYNTAX DisplayString
	MAX-ACCESS read-only
	STATUS current
	DESCRIPTION "Manufacturer ID codes"
::= { cSrvCardIdentEntry 3 }

cSrvCardIdentFunc OBJECT-TYPE
	SYNTAX DisplayString
	MAX-ACCESS read-only
	STATUS current
	DESCRIPTION "Function ID code"
::= { cSrvCardIdentEntry 4 }

cSrvCardIdentPCI OBJECT-TYPE
	SYNTAX DisplayString
	MAX-ACCESS read-only
	STATUS current
	DESCRIPTION "PCI ID"
::= { cSrvCardIdentEntry 5 }

cSrvCardConfTable OBJECT-TYPE
	SYNTAX SEQUENCE OF CSrvCardConfEntry
	MAX-ACCESS not-accessible
	STATUS current
	DESCRIPTION "This table has the socket configuration "
::= { cSrvPcmcia 3 }

cSrvCardConfEntry OBJECT-TYPE
	SYNTAX CSrvCardConfEntry
	MAX-ACCESS not-accessible
	STATUS current
	DESCRIPTION "One particular association between PCMCIA socket and its configuration"
	INDEX { cSrvCardConfIndex }
::= { cSrvCardConfTable 1 }

CSrvCardConfEntry ::= SEQUENCE {
	cSrvCardConfIndex Integer32,
	cSrvCardConfPower DisplayString,
	cSrvCardConfType DisplayString ,
	cSrvCardConfInter DisplayString,
	cSrvCardConfFunc DisplayString,
	cSrvCardConfCardv DisplayString,
	cSrvCardConfPort1 DisplayString,
	cSrvCardConfPort2 DisplayString
}

cSrvCardConfIndex OBJECT-TYPE
	SYNTAX Integer32(0..2)
	MAX-ACCESS read-only
	STATUS current
	DESCRIPTION "number to identifier the socket PCMCIA"
::= { cSrvCardConfEntry 1 }

cSrvCardConfPower OBJECT-TYPE
	SYNTAX DisplayString
	MAX-ACCESS read-only
	STATUS current
	DESCRIPTION "Power Settings"
::= { cSrvCardConfEntry 2 }

cSrvCardConfType OBJECT-TYPE
	SYNTAX DisplayString
	MAX-ACCESS read-only
	STATUS current
	DESCRIPTION "Interface Type"
::= { cSrvCardConfEntry 3 }

cSrvCardConfInter OBJECT-TYPE
	SYNTAX DisplayString
	MAX-ACCESS read-only
	STATUS current
	DESCRIPTION "Interrupt number"
::= { cSrvCardConfEntry 4 }

cSrvCardConfFunc OBJECT-TYPE
	SYNTAX DisplayString
	MAX-ACCESS read-only
	STATUS current
	DESCRIPTION "function"
::= { cSrvCardConfEntry 5 }

cSrvCardConfCardv OBJECT-TYPE
	SYNTAX DisplayString
	MAX-ACCESS read-only
	STATUS current
	DESCRIPTION "Card values"
::= { cSrvCardConfEntry 6 }

cSrvCardConfPort1 OBJECT-TYPE
	SYNTAX DisplayString
	MAX-ACCESS read-only
	STATUS current
	DESCRIPTION "I/O Port 1"
::= { cSrvCardConfEntry 7 }

cSrvCardConfPort2 OBJECT-TYPE
	SYNTAX DisplayString
	MAX-ACCESS read-only
	STATUS current
	DESCRIPTION "I/O Port 2"
::= { cSrvCardConfEntry 8 }

cSrvCardStatusTable OBJECT-TYPE
	SYNTAX SEQUENCE OF CSrvCardStatusEntry
	MAX-ACCESS not-accessible
	STATUS current
	DESCRIPTION "This table has the current socket status flags "
::= { cSrvPcmcia 4 }

cSrvCardStatusEntry OBJECT-TYPE
	SYNTAX CSrvCardStatusEntry
	MAX-ACCESS not-accessible
	STATUS current
	DESCRIPTION "One particular association between PCMCIA socket and its status"
	INDEX { cSrvCardStatusIndex }
::= { cSrvCardStatusTable 1 }

CSrvCardStatusEntry ::= SEQUENCE {
	cSrvCardStatusIndex Integer32,
	cSrvCardStatusCard DisplayString,
	cSrvCardStatusFunc DisplayString
}

cSrvCardStatusIndex OBJECT-TYPE
	SYNTAX Integer32(0..2)
	MAX-ACCESS read-only
	STATUS current
	DESCRIPTION "number to identifier the socket PCMCIA"
::= { cSrvCardStatusEntry 1 }

cSrvCardStatusCard OBJECT-TYPE
	SYNTAX DisplayString
	MAX-ACCESS read-only
	STATUS current
	DESCRIPTION "Current Card State"
::= { cSrvCardStatusEntry 2 }

cSrvCardStatusFunc OBJECT-TYPE
	SYNTAX DisplayString
	MAX-ACCESS read-only
	STATUS current
	DESCRIPTION "Current Function"
::= { cSrvCardStatusEntry 3 }


--
--    The cSrvConf group
--

--    CServer configuration objects:
 
--    Current Digital Networks CServer Configuration core mib table entries :
--	cSrvHostName		OBJECT-TYPE		::= { cSrvConf 1 }
--	cSrvConsoleBanner		OBJECT-TYPE		::= { cSrvConf 2 }
--	cSrvMotd			OBJECT-TYPE		::= { cSrvConf 3 }
--	cSrvEthItf			OBJECT-IDENTITY	::= { cSrvConf 4 }
--	cSrvNameService		OBJECT-IDENTITY	::= { cSrvConf 5 }  
--	cSrvSerialPortConf	OBJECT-IDENTITY	::= { cSrvConf 6 }

cSrvHostName	OBJECT-TYPE
	SYNTAX		DisplayString (SIZE (1..40))
	MAX-ACCESS		read-write
	STATUS		current
	DESCRIPTION	"The Host Name "
::= { cSrvConf 1 }                              

cSrvConsoleBanner	OBJECT-TYPE
	SYNTAX		DisplayString (SIZE (1..255))
	MAX-ACCESS		read-write
	STATUS		current
	DESCRIPTION	"The console banner "
::= { cSrvConf 2 }                              

cSrvMotd	OBJECT-TYPE
	SYNTAX		DisplayString (SIZE (0..255))
	MAX-ACCESS		read-write
	STATUS		current
	DESCRIPTION	"The motd message "
::= { cSrvConf 3 }                              

cSrvEthItf	OBJECT-IDENTITY
	STATUS     	current
	DESCRIPTION "The configuration of the Ethernet Interface"   
::= { cSrvConf 4 }

cSrvEthDhcpc	OBJECT-TYPE
	SYNTAX	INTEGER	{
			inactive(0),	-- DHCP is inactive
			active(1),	-- DHCP is active
			restore(2)	-- DHCP is active and CServer saves the last parameters 
					-- assigned by the server
			}
	MAX-ACCESS		read-write
	STATUS		current
	DESCRIPTION	"The Cserver can request all of its ethernet parameters 
				 to a DHCP server"
::= { cSrvEthItf 1 }

cSrvEthIPaddr	OBJECT-TYPE
	SYNTAX		IpAddress
	MAX-ACCESS		read-write
	STATUS		current
	DESCRIPTION	"This is the IP address of the Ethernet Interface"
::= { cSrvEthItf 2 }

cSrvEthIPmask		OBJECT-TYPE
	SYNTAX		IpAddress
	MAX-ACCESS		read-write
	STATUS		current
	DESCRIPTION	"The mask fot the Ethernet network"
::= { cSrvEthItf 3 }

cSrvEthMTU		OBJECT-TYPE
	SYNTAX		Integer32
	MAX-ACCESS		read-write
	STATUS		current
	DESCRIPTION	"The Maximum Transmission Unit size, wich determines 
				 whether or not packets should be broken up"
::= { cSrvEthItf 4 }

cSrvEthIPaddr2	OBJECT-TYPE
	SYNTAX		IpAddress
	MAX-ACCESS		read-write
	STATUS		current
	DESCRIPTION	"The Ethernet secondary IP address"
::= { cSrvEthItf 5 }

cSrvEthIPmask2	OBJECT-TYPE
	SYNTAX		IpAddress
	MAX-ACCESS		read-write
	STATUS		current
	DESCRIPTION	"The Ethernet secondary IP mask"
::= { cSrvEthItf 6 }

cSrvNameService	OBJECT-IDENTITY
	STATUS		current
	DESCRIPTION	"The Name Service configuration"
::= { cSrvConf 5 }  

cSrvResolverOrder	OBJECT-TYPE
	SYNTAX		DisplayString (SIZE (0..15))
	MAX-ACCESS		read-write
	STATUS		current
	DESCRIPTION	"It specifies how host lookups are to be performed.
				 Valid values : empty, 'hosts', 'bind', 'hosts, bind', 
				 'bind, hosts' "
::= { cSrvNameService 1 }
                   
cSrvMultipleIP	OBJECT-TYPE
	SYNTAX		DisplayString (SIZE (0..3))
	MAX-ACCESS		read-write
	STATUS		current
	DESCRIPTION	"Valid values are ON or OFF. If set to ON, the resolve 
				 library will return all valid addresses for a host 
				 that appears in the /etc/hosts file, instead of only 
				 the first.  "
::= { cSrvNameService 2 }

cSrvDNSserv		OBJECT-IDENTITY
	STATUS		current
	DESCRIPTION	"The DNS server configuration"
::= { cSrvNameService 3 }

cSrvDNSpriserv	OBJECT-TYPE
	SYNTAX		IpAddress
	MAX-ACCESS		read-write
	STATUS		current
	DESCRIPTION	"Internet Address (in dot notation) of primary name 
			 server that the resolver should query."
::= { cSrvDNSserv 1 }
 
cSrvDNSsecserv	OBJECT-TYPE
	SYNTAX		IpAddress
	MAX-ACCESS		read-write
	STATUS		current
	DESCRIPTION	"Internet Address (in dot notation) of secondary name 
			 server that the resolver should query."
::= { cSrvDNSserv 2 }

cSrvDNSdomain		OBJECT-TYPE
	SYNTAX		DisplayString (SIZE (1..40))
	MAX-ACCESS		read-write
	STATUS		current
	DESCRIPTION	"Local domain name ."
::= { cSrvDNSserv 3 }

cSrvSerialPortConf	OBJECT-IDENTITY
	STATUS		current
	DESCRIPTION	"The PortSlave configuration - pslave.conf file. 
			 It configures the all serial ports."
::= { cSrvConf 6 }  

cSrvSerialGlobal		OBJECT-IDENTITY
	STATUS		current
	DESCRIPTION	"These parameters have the prefix conf. in 
			 the pslave.conf file"
::= { cSrvSerialPortConf 1 }

cSrvSerialInclude	OBJECT-TYPE
	SYNTAX		DisplayString (SIZE (0..40))
	MAX-ACCESS	read-write
	STATUS		current
	DESCRIPTION	"File used in centralized management."
::= { cSrvSerialGlobal 1 }

cSrvSerialNFS		OBJECT-TYPE
	SYNTAX		DisplayString (SIZE (0..50))
	MAX-ACCESS	read-write
	STATUS		current
	DESCRIPTION	"Remote Network File System where data buffering will be 
			 written instead of the default directory '/var/run/DB'."
::= { cSrvSerialGlobal 2 }

cSrvSerialLockDir		OBJECT-TYPE
	SYNTAX		DisplayString (SIZE (0..50))
	MAX-ACCESS	read-write
	STATUS		current
	DESCRIPTION	"The lock directory for the CServer."
::= { cSrvSerialGlobal 3 }

cSrvSerialRlogin		OBJECT-TYPE
	SYNTAX		DisplayString (SIZE (0..50))
	MAX-ACCESS		read-write
	STATUS		current
	DESCRIPTION	"Location of the rlogin binary that accepts the -i flag."
::= { cSrvSerialGlobal 4 }

cSrvSerialPppd	OBJECT-TYPE
	SYNTAX		DisplayString (SIZE (0..50))
	MAX-ACCESS	read-write
	STATUS		current
	DESCRIPTION	"Location of the pppd binary."
::= { cSrvSerialGlobal 5 }

cSrvSerialTelnet	OBJECT-TYPE
	SYNTAX		DisplayString (SIZE (0..50))
	MAX-ACCESS	read-write
	STATUS		current
	DESCRIPTION "Location of the telnet application"
::= { cSrvSerialGlobal 6 }

cSrvSerialSsh		OBJECT-TYPE
	SYNTAX		DisplayString (SIZE (0..50))
	MAX-ACCESS	read-write
	STATUS		current
	DESCRIPTION	"Location of the ssh application"
::= { cSrvSerialGlobal 7 }

cSrvSerialLocalLogins	OBJECT-TYPE
	SYNTAX		INTEGER {
				off(0),           
				on(1)   -- possible to login to the CServer directly by placing a !
			}
	MAX-ACCESS	read-write
	STATUS		current
	DESCRIPTION "This parameter is only necessary when authentication is 
				 being performed for a port.
				 This is useful if the Radius authentication server is down."
::= { cSrvSerialGlobal 8 }

cSrvSerialFacility	OBJECT-TYPE
	SYNTAX		Integer32
	MAX-ACCESS	read-write
	STATUS		current
	DESCRIPTION	"This value (0-7) is the Local facility sent to the syslog daemon."
::= { cSrvSerialGlobal 9 }

cSrvSerialDBFacility	OBJECT-TYPE
	SYNTAX		Integer32
	MAX-ACCESS	read-write
	STATUS		current
	DESCRIPTION	"This value (0-7) is the Local facility sent to the syslog 
			 daemon with the data when ."
::= { cSrvSerialGlobal 10 }

cSrvSerialGroupTable	OBJECT-TYPE
	SYNTAX		SEQUENCE OF CSrvGroupEntry
	MAX-ACCESS	not-accessible
	STATUS		current
	DESCRIPTION	"This associates group name and its users"
::= { cSrvSerialGlobal 11 }

cSrvgroupEntry	OBJECT-TYPE
	SYNTAX		CSrvGroupEntry
	MAX-ACCESS	not-accessible
	STATUS		current
	DESCRIPTION	"One particular association between group name and its users"
	INDEX		{ cSrvGroupIndex }
::= { cSrvSerialGroupTable 1 }

CSrvGroupEntry ::= SEQUENCE  {
	cSrvGroupIndex	Integer32,
	cSrvGroupName	DisplayString,
	cSrvGroupUsers	DisplayString
}

cSrvGroupIndex	OBJECT-TYPE
	SYNTAX		InterfaceIndexOrZero	
	MAX-ACCESS	read-only
	STATUS		current
	DESCRIPTION	"number to identifier the group"
::= { cSrvgroupEntry  1 }                              

cSrvGroupName	OBJECT-TYPE
	SYNTAX		DisplayString (SIZE (0..20))
	MAX-ACCESS	read-write
	STATUS		current
	DESCRIPTION	"The Group Name "
::= { cSrvgroupEntry  2 }                              

cSrvGroupUsers	OBJECT-TYPE
	SYNTAX		DisplayString (SIZE (0..80))
	MAX-ACCESS	read-write
	STATUS		current
	DESCRIPTION	"The users names "
::= { cSrvgroupEntry  3 }                              

cSrvSerialSpec	OBJECT-IDENTITY
	STATUS		current
	DESCRIPTION	"These parameters have the prefix all. or sxx. in the pslave.conf file"
::= { cSrvSerialPortConf 2 }

cSrvSerialPortTable	OBJECT-TYPE
	SYNTAX		SEQUENCE OF CSrvSPortEntry
	MAX-ACCESS	not-accessible
	STATUS		current
	DESCRIPTION 	"This is the specific configuration to serial port"
::= { cSrvSerialSpec 1 }

cSrvsportEntry	OBJECT-TYPE
	SYNTAX		CSrvSPortEntry
	MAX-ACCESS	not-accessible
	STATUS		current
	DESCRIPTION	"One particular serial port configuration"
	INDEX		{ cSrvSPortNumber }
::= { cSrvSerialPortTable 1 }

CSrvSPortEntry ::= SEQUENCE  {
	cSrvSPortNumber		InterfaceIndexOrZero,	-- 0 == all.  X == ttyX sX.
	cSrvSPortTty		DisplayString,		-- associate device
	cSrvSPortName		DisplayString,		-- alias name
	cSrvSPortSpeed		INTEGER,		-- physical port configuration
	cSrvSPortDataSize		Integer32,
	cSrvSPortStopBits		Integer32,
	cSrvSPortParity		DisplayString,
	cSrvSPortFlowCtrl		DisplayString,
	cSrvSPortDTRdelay		Integer32,
	cSrvSPortDCDCtrl		INTEGER,
	cSrvSPortLogUtmp		INTEGER,		-- log into UTMP
	cSrvSPortLogWtmp		INTEGER,		-- log into WTMP
	cSrvSPortLogform		DisplayString,
	cSrvSPortAuthtype		DisplayString,		-- authentication type
	cSrvSPortAuthSrv1		IpAddress,	-- IP address of the primary authentication server
	cSrvSPortAccSrv1		IpAddress,	-- IP address of the primarty accounting server
	cSrvSPortAuthTmo		Integer32,	-- time out per authentication query
	cSrvSPortAuthRetr		Integer32,	-- authentication number of retries
	cSrvSPortAuthSrv2		IpAddress,	-- IP address of the secondary authentication server
	cSrvSPortAccSrv2		IpAddress,	-- IP address of the secondary accounting server
	cSrvSPortAuthSecret	DisplayString,	-- secret used in authentication
	cSrvSPortAuthRadP		INTEGER,	-- accept RADIUS' user without password
	cSrvSPortAuthAcc		DisplayString,	-- access restrition on Users
	cSrvSPortProtocol		DisplayString,	-- Profile
	cSrvSPortRemoteIP		DisplayString,	-- remote IP address
	cSrvSPortSocketPort	DisplayString,	-- number of socket port
	cSrvSPortRemHost		IpAddress,	-- IP address of the remote Host
	cSrvSPortBanner		DisplayString,	-- Banner
	cSrvSPortPrompt		DisplayString,	-- Login prompt
	cSrvSPortTermType		DisplayString,	-- terminal type
	cSrvSPortAutomUsr		DisplayString,	-- automatic user
	cSrvSPortNetMask		IpAddress,	-- net mask
	cSrvSPortPppMtu		Integer32,
	cSrvSPortPppMru		Integer32,
	cSrvSPortPppOptions	DisplayString,
	cSrvSPortPppFoption	DisplayString,
	cSrvSPortModemChat	DisplayString,	-- initchat send to modem
	cSrvSPortSttyCmd		DisplayString,
	cSrvSPortSockTx		Integer32,	-- socket transmission interval
	cSrvSPortSockPoll		Integer32,	-- socket polling interval
	cSrvSPortSockIdle		Integer32,	-- socket idle timeout
	cSrvSPortDBsize		Integer32,	-- maximum size of the data buffering file
	cSrvSPortDBtime		INTEGER,	-- data buffering with/without timestamp
	cSrvSPortDBmode		DisplayString,	-- data bufferinf mode circ or line
	cSrvSPortDBsyslog		Integer32,	-- size of the data send to syslog
	cSrvSPortDBmenu		INTEGER,	-- menu of the data buffering
	cSrvSPortDBalarm		INTEGER,	-- use alarm generating feature
	cSrvSPortSSHbreak		DisplayString,	-- break sequence (SSH)
	cSrvSPortSniffSess	DisplayString,	-- sniff session type
	cSrvSPortSniffAdm		DisplayString,	-- admin users to sniff
	cSrvSPortSniffEsc		DisplayString,	-- escape char to sniff session
	cSrvSPortSniffMsess	DisplayString,	-- multiple session
	cSrvSPortTelnetMode	INTEGER,	-- telnet client mode
	cSrvSPortSysBufSess	INTEGER,	-- syslog buffering at all times
	cSrvSPortLFSuppress	INTEGER,	-- LF suppression in socket_server session
	cSrvSPortAutoInput	DisplayString,  -- Input string to auto answer 
	cSrvSPortAutoOutput	DisplayString,  -- Output string to auto answer
	cSrvSPortPmType 		DisplayString,  -- Power Management IPDU type
	cSrvSPortPmUsers	 	DisplayString,  -- Power Management IPDU users
	cSrvSPortPmOutlet 	DisplayString,  -- Power Management Outlets
	cSrvSPortPmKey 		DisplayString,  -- Power Management Hotkey
	cSrvSPortPmNOutlets 	Integer32 	-- Power Management IPDU number of outlets 
}

cSrvSPortNumber	OBJECT-TYPE
	SYNTAX		InterfaceIndexOrZero	
	MAX-ACCESS	read-only
	STATUS		current
	DESCRIPTION	"number to identifier the serial port. Value 0 is ALL."
::= { cSrvsportEntry 1 }

cSrvSPortTty		OBJECT-TYPE
	SYNTAX		DisplayString (SIZE (0..25))
	MAX-ACCESS	read-write
	STATUS		current
	DESCRIPTION	"The device name for the serial port."
::= { cSrvsportEntry 2 }

cSrvSPortName		OBJECT-TYPE
	SYNTAX		DisplayString (SIZE (0..40))
	MAX-ACCESS	read-write
	STATUS		current
	DESCRIPTION	"Alias name given to the server connected to the serial port."
::= { cSrvsportEntry 3 }

cSrvSPortSpeed	OBJECT-TYPE
	SYNTAX		INTEGER {
				s50bps(50), s75bps(75), s110bps(110), s134bps(134), 
				s150bps(150), s200bps(200), s300bps(300), s600bps(600), 
				s1200bps(1200), s1800bps(1800),
				s2400bps(2400), s4800bps(4800), 
				s9600bps(9600), s14400bps(14400), 
				s19200bps(19200), s28800bps(28800), 
				s38400bps(38400), s57600bps(57600), 
				s115200bps(115200), s230400bps(230400), 
				s460800bps(460800)
			}	
	MAX-ACCESS	read-write
	STATUS		current
	DESCRIPTION	"The speed for serial port."
::= { cSrvsportEntry 4 }

cSrvSPortDataSize	OBJECT-TYPE
	SYNTAX		Integer32 (4..8)
	MAX-ACCESS	read-write
	STATUS		current
	DESCRIPTION	"The data size for serial port."
::= { cSrvsportEntry 5 }

cSrvSPortStopBits	OBJECT-TYPE
	SYNTAX		Integer32 (1..2)
	MAX-ACCESS	read-write
	STATUS		current
	DESCRIPTION	"The number of stop bits for serial port."
::= { cSrvsportEntry 6 }

cSrvSPortParity	OBJECT-TYPE
	SYNTAX		DisplayString (SIZE (0..5))
	MAX-ACCESS	read-write
	STATUS		current
	DESCRIPTION	"The parity for serial port."
::= { cSrvsportEntry 7 }

cSrvSPortFlowCtrl	OBJECT-TYPE
	SYNTAX		DisplayString (SIZE (0..5))
	MAX-ACCESS	read-write
	STATUS		current
	DESCRIPTION	"The flow control for serial port."
::= { cSrvsportEntry 8 }

cSrvSPortDTRdelay	OBJECT-TYPE
	SYNTAX		Integer32
	MAX-ACCESS	read-write
	STATUS		current
	DESCRIPTION	"This specifies how long (in miliseconds) a DTR signal
				 will be turned off before it is turned on again."
::= { cSrvsportEntry 9 }

cSrvSPortDCDCtrl	OBJECT-TYPE
	SYNTAX		INTEGER {
				notctrl(0),  
				control(1)	   
			}
	MAX-ACCESS	read-write
	STATUS		current
	DESCRIPTION	"DCD signal controls the connection request." 
::= { cSrvsportEntry 10 }

cSrvSPortLogUtmp	OBJECT-TYPE
	SYNTAX		INTEGER {
				inactive(0),  
				active(1)	   
			}
	MAX-ACCESS	read-write
	STATUS		current
	DESCRIPTION	"CServer update the login records in /var/run/utmp file." 
::= { cSrvsportEntry 11 }

cSrvSPortLogWtmp	OBJECT-TYPE
	SYNTAX		INTEGER {
				inactive(0),  
				active(1)	   
			}
	MAX-ACCESS	read-write
	STATUS		current
	DESCRIPTION	"CServer update the login records in /var/run/wtmp file." 
::= { cSrvsportEntry 12 }

cSrvSPortLogform	OBJECT-TYPE
	SYNTAX		DisplayString (SIZE (0..40))
	MAX-ACCESS	read-write
	STATUS		current
	DESCRIPTION	"This is the format to write login record." 
::= { cSrvsportEntry 13 }

cSrvSPortAuthtype		OBJECT-TYPE
	SYNTAX		DisplayString (SIZE (0..25))
	MAX-ACCESS	read-write
	STATUS		current
	DESCRIPTION	"Authentication type : ." 
::= { cSrvsportEntry 14 }

cSrvSPortAuthSrv1	OBJECT-TYPE
	SYNTAX		IpAddress
	MAX-ACCESS	read-write
	STATUS		current
	DESCRIPTION	"IP address of the primary authentication server." 
::= { cSrvsportEntry 15 }

cSrvSPortAccSrv1	OBJECT-TYPE
	SYNTAX		IpAddress
	MAX-ACCESS	read-write
	STATUS		current
	DESCRIPTION	"IP address of the primary accounting server." 
::= { cSrvsportEntry 16 }

cSrvSPortAuthTmo	OBJECT-TYPE
	SYNTAX		Integer32
	MAX-ACCESS	read-write
	STATUS		current
	DESCRIPTION	"This is the timeout (in seconds) for authentication 
			query to be answered." 
::= { cSrvsportEntry 17 }

cSrvSPortAuthRetr	OBJECT-TYPE
	SYNTAX		Integer32
	MAX-ACCESS	read-write
	STATUS		current
	DESCRIPTION	"This defines the number of times each server is tried 
			before another is contacted." 
::= { cSrvsportEntry 18 }

cSrvSPortAuthSrv2	OBJECT-TYPE
	SYNTAX		IpAddress
	MAX-ACCESS	read-write
	STATUS		current
	DESCRIPTION	"IP address of the secondary authentication server." 
::= { cSrvsportEntry 19 }

cSrvSPortAccSrv2	OBJECT-TYPE
	SYNTAX		IpAddress
	MAX-ACCESS	read-write
	STATUS		current
	DESCRIPTION	"IP address of the secondary accounting server." 
::= { cSrvsportEntry 20 }

cSrvSPortAuthSecret	OBJECT-TYPE
	SYNTAX		DisplayString (SIZE (0..40))
	MAX-ACCESS	read-write
	STATUS		current
	DESCRIPTION	"This is the shared secret with authentciation servers." 
::= { cSrvsportEntry 21 }

cSrvSPortAuthRadP	OBJECT-TYPE
	SYNTAX		INTEGER {
				inactive(0),  
				active(1)	   
			}
	MAX-ACCESS	read-write
	STATUS		current
	DESCRIPTION	"To accept Radius' user without password." 
::= { cSrvsportEntry 22 }

cSrvSPortAuthAcc	OBJECT-TYPE
	SYNTAX		DisplayString (SIZE (0..40))
	MAX-ACCESS	read-write
	STATUS		current
	DESCRIPTION	"access restrition on Users." 
::= { cSrvsportEntry 23 }

cSrvSPortProtocol	OBJECT-TYPE
	SYNTAX		DisplayString (SIZE (0..40))
	MAX-ACCESS	read-write
	STATUS		current
	DESCRIPTION	"Defines the port serial's protocol." 
::= { cSrvsportEntry 24 }

cSrvSPortRemoteIP	OBJECT-TYPE
	SYNTAX		DisplayString (SIZE (0..20))
	MAX-ACCESS	read-write
	STATUS		current
	DESCRIPTION	"This is the default IP address of the serial port." 
::= { cSrvsportEntry 25 }

cSrvSPortSocketPort	OBJECT-TYPE	
	SYNTAX		DisplayString (SIZE (0..10))
	MAX-ACCESS	read-write
	STATUS		current
	DESCRIPTION	"This defines an alternative labeling system for the serial port." 
::= { cSrvsportEntry 26 }

cSrvSPortRemHost	OBJECT-TYPE
	SYNTAX		IpAddress
	MAX-ACCESS	read-write
	STATUS		current
	DESCRIPTION	"The IP address of the host to which the serial port will connect." 
::= { cSrvsportEntry 27 }

cSrvSPortBanner	OBJECT-TYPE
	SYNTAX		DisplayString (SIZE (0..250))
	MAX-ACCESS	read-write
	STATUS		current
	DESCRIPTION	"This defines the banner." 
::= { cSrvsportEntry 28 }

cSrvSPortPrompt	OBJECT-TYPE
	SYNTAX		DisplayString (SIZE (0..250))
	MAX-ACCESS	read-write
	STATUS		current
	DESCRIPTION	"This defines the login prompt to the serial port." 
::= { cSrvsportEntry 29 }

cSrvSPortTermType	OBJECT-TYPE
	SYNTAX		DisplayString (SIZE (0..20))
	MAX-ACCESS	read-write
	STATUS		current
	DESCRIPTION	"This defines the terminal type." 
::= { cSrvsportEntry 30 }

cSrvSPortAutomUsr	OBJECT-TYPE
	SYNTAX		DisplayString (SIZE (0..40))
	MAX-ACCESS	read-write
	STATUS		current
	DESCRIPTION	"This defines the automatic user." 
::= { cSrvsportEntry 31 }

cSrvSPortNetMask	OBJECT-TYPE
	SYNTAX		IpAddress
	MAX-ACCESS	read-write
	STATUS		current
	DESCRIPTION	"The network mask used in dial in connection." 
::= { cSrvsportEntry 32 }

cSrvSPortPppMtu	OBJECT-TYPE
	SYNTAX		Integer32
	MAX-ACCESS	read-write
	STATUS		current
	DESCRIPTION	"The PPP MTU - dial in connection." 
::= { cSrvsportEntry 33 }

cSrvSPortPppMru	OBJECT-TYPE
	SYNTAX		Integer32
	MAX-ACCESS	read-write
	STATUS		current
	DESCRIPTION	"The PPP MRU - dial in connection." 
::= { cSrvsportEntry 34 }

cSrvSPortPppOptions	OBJECT-TYPE
	SYNTAX		DisplayString
	MAX-ACCESS	read-write
	STATUS		current
	DESCRIPTION	"The PPP options when CServer autodetects the PPP session ." 
::= { cSrvsportEntry 35 }

cSrvSPortPppFoption	OBJECT-TYPE
	SYNTAX		DisplayString
	MAX-ACCESS	read-write
	STATUS		current
	DESCRIPTION	"The PPP forced options when the user has already been authenticated." 
::= { cSrvsportEntry 36 }

cSrvSPortModemChat	OBJECT-TYPE
	SYNTAX		DisplayString
	MAX-ACCESS	read-write
	STATUS		current
	DESCRIPTION	"The initchat send to modem connected." 
::= { cSrvsportEntry 37 }

cSrvSPortSttyCmd	OBJECT-TYPE
	SYNTAX		DisplayString (SIZE (0..180))
	MAX-ACCESS	read-write
	STATUS		current
	DESCRIPTION	"the tty settings after socket connection is established." 
::= { cSrvsportEntry 38 }

cSrvSPortSockTx	OBJECT-TYPE	
	SYNTAX		Integer32
	MAX-ACCESS	read-write
	STATUS		current
	DESCRIPTION	"Defines the delay (in miliseconds) before transmission to
			 the Ethernet of data received through a serial port ." 
::= { cSrvsportEntry 39 }

cSrvSPortSockPoll	OBJECT-TYPE
	SYNTAX		Integer32
	MAX-ACCESS	read-write
	STATUS		current
	DESCRIPTION	"Keep-alive timer (miliseconds) to the TCP connection ." 
::= { cSrvsportEntry 40 }

cSrvSPortSockIdle	OBJECT-TYPE
	SYNTAX		Integer32
	MAX-ACCESS	read-write
	STATUS		current
	DESCRIPTION	"The idle timeout in seconds ." 
::= { cSrvsportEntry 41 }

cSrvSPortDBsize	OBJECT-TYPE
	SYNTAX		Integer32
	MAX-ACCESS	read-write
	STATUS		current
	DESCRIPTION	"Maximum size of the data buffering file." 
::= { cSrvsportEntry 42 }

cSrvSPortDBtime	OBJECT-TYPE
	SYNTAX		INTEGER {
				inactive(0),
				active(1)
			}
	MAX-ACCESS	read-write
	STATUS		current
	DESCRIPTION	"Timestamp in data buffering." 
::= { cSrvsportEntry 43 }

cSrvSPortDBmode	OBJECT-TYPE
	SYNTAX		DisplayString (SIZE (0..5))
	MAX-ACCESS	read-write
	STATUS		current
	DESCRIPTION	"Data buffering mode : circ or line"
::= { cSrvsportEntry 44 }

cSrvSPortDBsyslog	OBJECT-TYPE
	SYNTAX		Integer32
	MAX-ACCESS	read-write
	STATUS		current
	DESCRIPTION	"size of the data buffering send to syslog." 
::= { cSrvsportEntry 45 }

cSrvSPortDBmenu	OBJECT-TYPE
	SYNTAX		INTEGER {
				displayMenu(0),
				inactive(1),
				displayDB(2),
				displayParc(3)
			}
	MAX-ACCESS	read-write
	STATUS		current
	DESCRIPTION	"Menu of the data buffering." 
::= { cSrvsportEntry 46 }

cSrvSPortDBalarm	OBJECT-TYPE
	SYNTAX		INTEGER {
				inactive(0),
				active(1)
			}
	MAX-ACCESS	read-write
	STATUS		current
	DESCRIPTION	"Generating Alarms." 
::= { cSrvsportEntry 47 }

cSrvSPortSSHbreak	OBJECT-TYPE
	SYNTAX		DisplayString (SIZE (0..16))
	MAX-ACCESS	read-write
	STATUS		current
	DESCRIPTION	"Break sequence - ssh session"
::= { cSrvsportEntry 48 }

cSrvSPortSniffSess	OBJECT-TYPE
	SYNTAX		DisplayString (SIZE (0..5))
	MAX-ACCESS	read-write
	STATUS		current
	DESCRIPTION	"Sniff session type"
::= { cSrvsportEntry 49 }

cSrvSPortSniffAdm	OBJECT-TYPE
	SYNTAX		DisplayString (SIZE (0..40))
	MAX-ACCESS	read-write
	STATUS		current
	DESCRIPTION	"List of admin users to sniff session"
::= { cSrvsportEntry 50 }

cSrvSPortSniffEsc	OBJECT-TYPE
	SYNTAX		DisplayString (SIZE (0..6))
	MAX-ACCESS	read-write
	STATUS		current
	DESCRIPTION	"Escape sequence used in sniff session"
::= { cSrvsportEntry 51 }

cSrvSPortSniffMsess	OBJECT-TYPE
	SYNTAX		DisplayString (SIZE (0..20))
	MAX-ACCESS	read-write
	STATUS		current
	DESCRIPTION	"Multiple sniff sessions"
::= { cSrvsportEntry 52 }

cSrvSPortTelnetMode	OBJECT-TYPE
	SYNTAX		INTEGER {
				text(0),
				binary(1)
			}
	MAX-ACCESS	read-write
	STATUS		current
	DESCRIPTION	"Mode negotiated by client telnet with the server"
::= { cSrvsportEntry 53 }

cSrvSPortSysBufSess	OBJECT-TYPE
	SYNTAX		INTEGER {
				yes(0),
				no(1)
			}
	MAX-ACCESS	read-write
	STATUS		current
	DESCRIPTION	"Syslog Buffering at all times"
::= { cSrvsportEntry 54 }

cSrvSPortLFSuppress	OBJECT-TYPE
	SYNTAX		INTEGER {
				inactive(0),
				active(1)
			}
	MAX-ACCESS	read-write
	STATUS		current
	DESCRIPTION	"LF suppression in socket_server session"
::= { cSrvsportEntry 55 }

cSrvSPortAutoInput	OBJECT-TYPE
	SYNTAX		DisplayString (SIZE (0..40))
	MAX-ACCESS	read-write
	STATUS		current
	DESCRIPTION	"This string is used to auto answer. It's the input string"
::= { cSrvsportEntry 56 }

cSrvSPortAutoOutput	OBJECT-TYPE
	SYNTAX		DisplayString (SIZE (0..40))
	MAX-ACCESS	read-write
	STATUS		current
	DESCRIPTION	"This string is used to auto answer. It's the output string"
::= { cSrvsportEntry 57 }

cSrvSPortPmType		OBJECT-TYPE
	SYNTAX		DisplayString (SIZE (0..20))
	MAX-ACCESS	read-write
	STATUS		current
	DESCRIPTION	"IPDU type, when the port protocol is configured as IPDU"
::= { cSrvsportEntry 58 }

cSrvSPortPmUsers		OBJECT-TYPE
	SYNTAX		DisplayString (SIZE (0..40))
	MAX-ACCESS	read-write
	STATUS		current
	DESCRIPTION	"List of users which can access the IPDU and their respective outlets"
::= { cSrvsportEntry 59 }

cSrvSPortPmOutlet		OBJECT-TYPE
	SYNTAX		DisplayString (SIZE (0..40))
	MAX-ACCESS	read-write
	STATUS		current
	DESCRIPTION	"List of <IPDU port>.<outlet> pairs, where the server is connected"
::= { cSrvsportEntry 60 }

cSrvSPortPmKey		OBJECT-TYPE
	SYNTAX		DisplayString (SIZE (0..8))
	MAX-ACCESS	read-write
	STATUS		current
	DESCRIPTION	"Hotkey to grant access to the Power Management from a Telnet/SSH session"
::= { cSrvsportEntry 61 }

cSrvSPortPmNOutlets	OBJECT-TYPE
	SYNTAX		Integer32
	MAX-ACCESS	read-write
	STATUS		current
	DESCRIPTION	"Number of outlets of the IPDU"
::= { cSrvsportEntry 62 }

--
--    The cSrvInfo Group
--

cSrvInfoSerialTable	OBJECT-TYPE
	SYNTAX		SEQUENCE OF CSrvISPortEntry
	MAX-ACCESS	not-accessible
	STATUS		current
	DESCRIPTION	"This is the information of the specific serial port"
::= { cSrvInfo 1 }

cSrvisPortEntry	OBJECT-TYPE
	SYNTAX		CSrvISPortEntry
	MAX-ACCESS	not-accessible
	STATUS		current
	DESCRIPTION	"One particular serial port "
	INDEX		{ cSrvISPortNumber }
::= { cSrvInfoSerialTable 1 }

CSrvISPortEntry ::= SEQUENCE  {
	cSrvISPortNumber	InterfaceIndex,      --  X == ttyX sX.
	cSrvISPortTty	DisplayString,         -- associate device
	cSrvISPortName	DisplayString,          -- alias name
	cSrvISPortSpeed	Integer32,
	cSrvISPortTxBytes	Counter32,          
	cSrvISPortRXBytes	Counter32,
	cSrvISPortErrFrame	Counter32,
	cSrvISPortErrParity	Counter32,
	cSrvISPortErrBreaks	Counter32,
	cSrvISPortErrOverrun	Counter32,
	cSrvISPortSigDTR		INTEGER,
	cSrvISPortSigCD		INTEGER,
	cSrvISPortSigDSR		INTEGER,
	cSrvISPortSigRTS		INTEGER,
	cSrvISPortSigCTS		INTEGER,
	cSrvISPortSigRI		INTEGER
 }

cSrvISPortNumber	OBJECT-TYPE
	SYNTAX		InterfaceIndex	
	MAX-ACCESS	read-only
	STATUS		current
	DESCRIPTION	"number to identifier the serial port."
::= { cSrvisPortEntry 1 }

cSrvISPortTty		OBJECT-TYPE
	SYNTAX		DisplayString	
	MAX-ACCESS	read-only
	STATUS		current
	DESCRIPTION	"The device name for the serial port."
::= { cSrvisPortEntry 2 }

cSrvISPortName		OBJECT-TYPE
	SYNTAX		DisplayString	
	MAX-ACCESS	read-only
	STATUS		current
	DESCRIPTION	"Alias name given to the server connected to the serial port."
::= { cSrvisPortEntry 3 }

cSrvISPortSpeed	OBJECT-TYPE
	SYNTAX		Integer32 
	MAX-ACCESS	read-only
	STATUS		current
	DESCRIPTION	"The speed for serial port."
::= { cSrvisPortEntry 4 }

cSrvISPortTxBytes	OBJECT-TYPE        
	SYNTAX		Counter32 
	MAX-ACCESS	read-only
	STATUS		current
	DESCRIPTION	"The number of transmited bytes by the serial port."
::= { cSrvisPortEntry 5 }

cSrvISPortRXBytes	OBJECT-TYPE
	SYNTAX		Counter32 
	MAX-ACCESS	read-only
	STATUS		current
	DESCRIPTION	"The number of received bytes by the serial port."
::= { cSrvisPortEntry 6 }

cSrvISPortErrFrame	OBJECT-TYPE
	SYNTAX		Counter32 
	MAX-ACCESS	read-only
	STATUS		current
	DESCRIPTION	"The number of frame error."
::= { cSrvisPortEntry 7 }

cSrvISPortErrParity	OBJECT-TYPE
	SYNTAX		Counter32 
	MAX-ACCESS	read-only
	STATUS		current
	DESCRIPTION	"The number of parity error."
::= { cSrvisPortEntry 8 }

cSrvISPortErrBreaks	OBJECT-TYPE	
	SYNTAX		Counter32 
	MAX-ACCESS	read-only
	STATUS		current
	DESCRIPTION	"The number of breaks error."
::= { cSrvisPortEntry 9 }

cSrvISPortErrOverrun	OBJECT-TYPE
	SYNTAX		Counter32 
	MAX-ACCESS	read-only
	STATUS		current
	DESCRIPTION	"The number of overrun error."
::= { cSrvisPortEntry 10 }

cSrvISPortSigDTR	OBJECT-TYPE
	SYNTAX		INTEGER {
				down(0),
				up(1)
			}
	MAX-ACCESS	read-only
	STATUS		current
	DESCRIPTION	"The state of DTR signal."
::= { cSrvisPortEntry 11 }

cSrvISPortSigCD	OBJECT-TYPE
	SYNTAX		INTEGER {
				down(0),
				up(1)
			}
	MAX-ACCESS	read-only
	STATUS		current
	DESCRIPTION	"The state of DCD signal."
::= { cSrvisPortEntry 12 }

cSrvISPortSigDSR	OBJECT-TYPE
	SYNTAX		INTEGER {
				down(0),
				up(1)
			}
	MAX-ACCESS	read-only
	STATUS		current
	DESCRIPTION	"The state of DSR signal."
::= { cSrvisPortEntry 13 }

cSrvISPortSigRTS	OBJECT-TYPE
	SYNTAX		INTEGER {
				down(0),
				up(1)
			}
	MAX-ACCESS	read-only
	STATUS		current
	DESCRIPTION	"The state of RTS signal."
::= { cSrvisPortEntry 14 }

cSrvISPortSigCTS	OBJECT-TYPE
	SYNTAX		INTEGER {
				down(0),
				up(1)
			}
	MAX-ACCESS	read-only
	STATUS		current
	DESCRIPTION	"The state of CTS signal."
::= { cSrvisPortEntry 15 }

cSrvISPortSigRI	OBJECT-TYPE
	SYNTAX		INTEGER {
				down(0),
				up(1)
			}
	MAX-ACCESS	read-only
	STATUS		current
	DESCRIPTION	"The state of RI signal."
::= { cSrvisPortEntry 16 }


--
--    The CServer Administration Group (cSrvAdm)
--

cSrvSave	OBJECT-TYPE
	SYNTAX		INTEGER {
				nosave(0),
				save(1)
			}
	MAX-ACCESS	read-write
	STATUS		current
	DESCRIPTION	"Exec saveconf command"
::= { cSrvAdm 1 }
                               
cSrvSerialHUP	OBJECT-TYPE
	SYNTAX		INTEGER {
				norestartportslave(0),
				restartportslave(1)
			}
	MAX-ACCESS    read-write
	STATUS          current
	DESCRIPTION     "Exec signal_ras hup command"
::= { cSrvAdm 2 }

END
